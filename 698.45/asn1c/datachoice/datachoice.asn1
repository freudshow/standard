DataChoice DEFINITIONS ::= BEGIN
	Data::=CHOICE {
		nullData [0] NULL,
		arrayData [1] SEQUENCE OF Data,
		structureData [2] SEQUENCE OF Data,
		boolData [3] BOOLEAN,
		bit-stringData [4] BIT STRING,
		double-longData [5] INTEGER,
		octet-stringData [9] OCTET STRING,
		visible-stringData [10] VisibleString
}
END
